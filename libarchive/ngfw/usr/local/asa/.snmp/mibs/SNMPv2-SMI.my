-- $Id: //depot/vermont/main/Xpix/snmp/mib-def-files/SNMPv2-SMI.my#1 $:
-- $Source$:
-- *****************************************************************
-- SNMPv2-SMI.my:  SNMPv2 Structure of Management Information
--
-- May 1994, Jeffrey T. Johnson
--
-- Copyright (c) 2002, 2016 by Cisco Systems, Inc.
-- All rights reserved.
-- 
-- *****************************************************************
--
--	The following was extracted from RFC 1902
--	All macro definitions have been removed because they are
--	predefined in the mib compiler

SNMPv2-SMI DEFINITIONS ::= BEGIN


-- the path to the root

org            OBJECT IDENTIFIER ::= { iso 3 }
dod            OBJECT IDENTIFIER ::= { org 6 }
internet       OBJECT IDENTIFIER ::= { dod 1 }

directory      OBJECT IDENTIFIER ::= { internet 1 }

mgmt           OBJECT IDENTIFIER ::= { internet 2 }
mib-2          OBJECT IDENTIFIER ::= { mgmt 1 }
transmission   OBJECT IDENTIFIER ::= { mib-2 10 }

experimental   OBJECT IDENTIFIER ::= { internet 3 }

private        OBJECT IDENTIFIER ::= { internet 4 }
enterprises    OBJECT IDENTIFIER ::= { private 1 }

security       OBJECT IDENTIFIER ::= { internet 5 }

snmpV2         OBJECT IDENTIFIER ::= { internet 6 }

-- transport domains
snmpDomains    OBJECT IDENTIFIER ::= { snmpV2 1 }

-- transport proxies
snmpProxys     OBJECT IDENTIFIER ::= { snmpV2 2 }

-- module identities
snmpModules    OBJECT IDENTIFIER ::= { snmpV2 3 }

END
